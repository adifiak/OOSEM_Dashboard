package I_PowerSupply {
    private import OOSEM::OOSEM_Metadata::*;
    private import D_PowerSupply::D_PowerSupply;

    #integration part def I_PowerSupply :> D_PowerSupply {
        //TODO: Auto-generated block skeleton
    }
}
