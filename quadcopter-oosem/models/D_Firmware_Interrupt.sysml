package D_Firmware_Interrupt {
    private import OOSEM::OOSEM_Metadata::*;
    private import D_FlightComputer::S_Firmware;

    #design part def D_Firmware_Interrupt :> S_Firmware {
        //TODO: Auto-generated block skeleton
    }
}
