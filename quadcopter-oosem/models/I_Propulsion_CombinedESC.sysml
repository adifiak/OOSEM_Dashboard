package I_Propulsion_CombinedESC {
    private import OOSEM::OOSEM_Metadata::*;
    private import D_Propulsion_CombinedESC::D_Propulsion_CombinedESC;

    #integration part def I_Propulsion_CombinedESC :> D_Propulsion_CombinedESC {
        //TODO: Auto-generated block skeleton
    }
}
