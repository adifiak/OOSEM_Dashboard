package D_CommunicationsModule {
    private import OOSEM::OOSEM_Metadata::*;
    private import D_Quadcopter::S_CommunicationsModule;

    #design part def D_CommunicationsModule :> S_CommunicationsModule {
        //TODO: Auto-generated block skeleton
    }
}
