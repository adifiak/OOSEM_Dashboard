package I_Firmware_Interrupt {
    private import OOSEM::OOSEM_Metadata::*;
    private import D_Firmware_Interrupt::D_Firmware_Interrupt;

    #integration part def I_Firmware_Interrupt :> D_Firmware_Interrupt {
        //TODO: Auto-generated block skeleton
    }
}
