package D_Firmware_Polling {
    private import OOSEM::OOSEM_Metadata::*;
    private import D_FlightComputer::S_Firmware;

    #design part def D_Firmware_Polling :> S_Firmware {
        //TODO: Auto-generated block skeleton
    }
}
