package I_Airframe {
    private import OOSEM::OOSEM_Metadata::*;
    private import D_Airframe::D_Airframe;

    #integration part def I_Airframe :> D_Airframe {
		//TODO: Auto-generated block skeleton
	}
}
