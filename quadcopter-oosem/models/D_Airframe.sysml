package D_Airframe {
    private import OOSEM::OOSEM_Metadata::*;
    private import D_Quadcopter::S_Airframe;

    #design part def D_Airframe :> S_Airframe {
		//TODO: Auto-generated block skeleton
	}
}
