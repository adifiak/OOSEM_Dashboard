package I_CommunicationsModule {
    private import OOSEM::OOSEM_Metadata::*;
    private import D_CommunicationsModule::D_CommunicationsModule;

    #integration part def I_CommunicationsModule :> D_CommunicationsModule {
        //TODO: Auto-generated block skeleton
    }
}
