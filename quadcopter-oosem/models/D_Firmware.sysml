package D_Firmware {
    private import OOSEM::OOSEM_Metadata::*;
    private import D_FlightComputer::S_Firmware;

    #design part def D_Firmware :> S_Firmware {
        //TODO: Auto-generated block skeleton
    }
}
