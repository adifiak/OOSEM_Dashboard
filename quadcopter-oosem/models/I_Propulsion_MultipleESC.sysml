package I_Propulsion_MultipleESC {
    private import OOSEM::OOSEM_Metadata::*;
    private import D_Propulsion_MultipleESC::D_Propulsion_MultipleESC;

    #integration part def I_Propulsion_MultipleESC :> D_Propulsion_MultipleESC {
        //TODO: Auto-generated block skeleton
    }
}
