package D_PowerSupply {
    private import OOSEM::OOSEM_Metadata::*;
    private import D_Quadcopter::S_PowerSupply;

    #design part def D_PowerSupply :> S_PowerSupply {
		//TODO: Auto-generated block skeleton
	}
}
